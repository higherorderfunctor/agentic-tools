[DOCUMENT]
TITLE: evidence

[GRAMMAR]
IMPORT_FROM_FILE: @repo

[NARRATIVE]
UID: NAR-SEMANTIC-LAYER-TYPE-EVIDENCE
TITLE: evidence
AUTHORED_BY: llm
WIDGET: prose
PLACE: screen
TAGS: EVIDENCE
STATEMENT: >>>
What happened this once. A measurement, a probe's finding, a proof that something was delivered.

Also: descriptive and particular in the grid ([LINK: DEC-NODE-FAMILIES]). On the sheet's day evidence hid in three places: a probe's STATUS, two measurements filed as INVARIANT, and proof of completion kept in the NOTES of finished work. The first two were retyped on 2026-08-30 -- the eight run probes and the two measurements are EVIDENCE now, keeping their SPIKE- and INV- prefixes under [LINK: DEC-UID-OUTLIVES-TYPE]; [LINK: MECH-SPIKE-IS-A-PIPELINE-TO-A-DECISION] is the reading that splits a probe into work, then evidence, then the decision it settles. Proof kept in NOTES is still where it was.

State: none. An optional SOURCE names where the observation came from.
<<<
PARENT_FP: >>>
DEC-NODE-FAMILIES:0000000
DEC-UID-OUTLIVES-TYPE:0000000
<<<
RELATIONS:
- TYPE: Parent
  VALUE: DEC-NODE-FAMILIES
  ROLE: Cites
- TYPE: Parent
  VALUE: DEC-UID-OUTLIVES-TYPE
  ROLE: Cites
