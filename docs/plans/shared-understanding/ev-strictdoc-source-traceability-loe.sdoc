[DOCUMENT]
TITLE: strictdoc source traceability: how it works and the LOE to extend it

[GRAMMAR]
IMPORT_FROM_FILE: @repo

[EVIDENCE]
UID: EV-STRICTDOC-SOURCE-TRACEABILITY-LOE
TITLE: strictdoc source traceability: how it works and the LOE to extend it
AUTHORED_BY: llm
SOURCE: four independent readers over the installed strictdoc 0.28.3 package and this worktree at 2f90b224, plus a scratch end-to-end Nix reader prototype and grammar ABI probes in the session scratchpad; strictdoc 0.28.3; 2026-09-02
STATEMENT: >>>
Paths: `strictdoc/...` is the installed 0.28.3 package at /nix/store/9khac7sfda0rzk6blqd3cnlwb7q3hsvz-strictdoc/lib/python3.14/site-packages/strictdoc/; bare repo paths are this worktree at 2f90b224; "scratch" is the session scratchpad's traceability/ directory, none of it committed.

How it works. Source traceability is opt-in through ProjectFeature.REQUIREMENT_TO_SOURCE_TRACEABILITY, absent from DEFAULT_FEATURES (strictdoc/core/project_config.py:98-138). strictdoc_config.py:81-87 does not set it and dev/scripts/sdoc_model.py:757 passes skip_source_files=True, so no source file is read today: the corpus's 49 File relations (35 nodes, VALUE only) get a path-existence check from dev/scripts/file-check.py:50-87 via checks/strictdoc-file-check.nix:63-64 and nothing else. With the feature on, the index builder walks every non-binary file under source_root_path (strictdoc/core/traceability_index_builder.py:153-219) and dispatches by suffix through a hard-coded if/endswith chain with no registry hook (strictdoc/backend/sdoc_source_code/reader_registry.py:34-53): .py, the C family and .rs get tree-sitter readers, .robot gets robot.api, and every other suffix (.nix, .ts, .sh, .json) gets a textX generic reader that knows only scope=file, line, range_start and range_end and discards a scope=function or scope=class line as prose, even one naming a nonexistent UID (grammar.py:19-48; measured on .nix and .ts: exit 0, nothing rendered). A reader fills a SourceFileTraceabilityInfo (models/source_file_info.py:41-70) with LanguageItems, which carry name, display_name, 1-based lines, code_byte_range and attributes but no kind field (models/language.py:16-114), plus markers that MarkerParser.parse (marker_parser.py:28-42) lifts from comments with the Lark grammar `@relation(UID[, UID...], scope=file|class|function|line|range_start|range_end[, role=X])` (comment_parser/marker_lexer.py:39; UID regex constants.py:7).

Backward, every marker UID must resolve or export fails (strictdoc/core/file_traceability_index.py:738-763). Forward, the .sdoc File block accepts ROLE, FORMAT, VALUE or PATH, ELEMENT, ID, LINE_RANGE, deprecated FUNCTION/CLASS, and HASH (strictdoc/backend/sdoc/grammar/type_system.py:42-59; models/reference.py:52-90); validate_and_resolve makes each a hard error when the path was not indexed (file_traceability_index.py:609-619), a language-item marker when ELEMENT: function or class plus ID matches a parsed item by name (:634-661, :855-929), two range markers for LINE_RANGE (:662-679), or a whole-file marker for anything else, an unknown ELEMENT: module or option included (:680-697, measured twice). An ID matching nothing is dropped silently: exit 0, no marker, absent from both pages (:709-721). The rendered kind label is reader-controlled through set_description, which is how Rust shows impl, trait and mod (reader_rust.py:334-390, 574-577) and how the scratch Nix prototype rendered `class config` and `function options.services.foo.enable()`. The JSON export this repo's checkers consume keeps only TYPE, FORMAT, VALUE and LINE_RANGE of a File relation (strictdoc/backend/json/json_generator.py:310-323), so resolved ranges live only in memory and in HTML. Two operational bounds: enabling the feature measured 12.32 s per export against 1.52 s on this tree, one error per run, binaries reported missing, and include_source_paths narrowing producing false positives (docs/plans/strictdoc-tooling/mech-file-relation-existence.sdoc:47-58); and per-file parses are pickled keyed on source mtime, size and md5 only, so a reader-code change does not invalidate them and no --no-cache flag exists (strictdoc/backend/sdoc/pickle_cache.py:16-77; measured stale).

Extending it. There is no ABC, Protocol or entry point; the registry's return type is a Union of five concrete readers (reader_registry.py:27-33). A reader is any object with supported_elements(), __init__(custom_tags=None), read(buf, file_path) returning a SourceFileTraceabilityInfo, and read_from_file(path); inside read() it parses with tree-sitter, walks with traverse_tree (tree_sitter_helpers.py:10-47), calls MarkerParser.parse per comment with a default_scope, runs language_item_marker_processor per marker, builds one LanguageItem per definition and ends with source_file_traceability_info_processor (processors/general_language_marker_processors.py:257-308). Templates: reader_python.py (391 lines, node walk), reader_c.py (539, comment adjacency, decl/def, custom_tags), reader_rust.py (729, the only Query-driven one, TS_QUERY at :45-194). Upstream's recipe, from the maintainer on issue #2345: find a grammar, then copy-and-paste by similarity with the C and Python readers. Registration needs no fork: strictdoc_config.py is an arbitrary module imported before the index is built (strictdoc/core/project_config.py:1236-1300) and both callers resolve SourceCodeReaderRegistry.get_reader at call time (caching_reader.py:81-83; backend/markdown/reader.py:1906), so reassigning that staticmethod from the repo's existing config injects a reader with zero package edits. The scratch prototype does exactly that in 77 lines (reader about 55, registry patch 5, create_config 3), and strictdoc export exits 0 with a backward `@relation(REQ-1, scope=function)` above a binding and forward `ELEMENT: function / ID: options.services.foo.enable` and `ELEMENT: class / ID: config` all rendering (scratch e2e/out/html/_source_files/src/mod.nix.html). The first-party route edits reader_registry.py:34-53, pyproject.toml:76-80 and uv.lock (upstream's flake is uv2nix) and then carries a patch in overlays/dev-tools/strictdoc.nix or an upstream PR with no contribution guidance (the JS/TS request #2214 has been open since 2025-05 with zero comments).

Grammar delivery: the package's $out holds bin/strictdoc only (overlays/dev-tools/strictdoc.nix:25-33), so a grammar is spliced by a makeWrapper --prefix PYTHONPATH wrapper on the venv interpreter, the packages/strictdoc-grammar/lib/mkExtract.nix:89-98 precedent; the devenv python3 (devenv.nix:156) cannot import strictdoc (measured). The nixpkgs tree-sitter-nix 0.3.0 binding drags tree-sitter-config, email-validator, dnspython and idna (measured working once added) and sits at ABI 13, exactly py-tree-sitter 0.25.2's MIN_COMPATIBLE_LANGUAGE_VERSION; the prototype instead loads the grammar's parser library through ctypes and the deprecated Language(int) path (scratch e2e/strictdoc_config.py:18-19). TypeScript's wheel (tree-sitter-typescript 0.23.2, ABI 14) splices with nothing extra. Kinds beyond function and class cost nothing as labels via set_description; as first-class ELEMENT or scope words they are a fork or an upstream PR, because LanguageItem has no kind and the vocabulary is closed in seven places (the LOE row below lists them). An external extractor, such as the ast-grep normalizer under packages/strictdoc-grammar/extract/ (which today extracts the grammar surface, not source), meets no ingest API: a JSON-hydrating reader builds the models by hand and runs the three marker processors plus the info processor (general_language_marker_processors.py:71-86, 181-200, 203-254, 257-308), still inside strictdoc's process and behind the same source-keyed cache.

The dirty-edge gap. strictdoc gives nothing at runtime. FileEntry.hash is documented in code as "Placeholder for drift-detection hash (no runtime functionality yet)" (models/reference.py:89-90), written back verbatim (backend/sdoc/writer.py:578-581; `strictdoc format` preserves it byte-for-byte, measured) and never computed or compared; the resolver keeps line numbers only (file_traceability_index.py:966-1019), so a renamed function silently stops matching. The only code-hashing logic is `manage auto-uid`, sha256(project + path + instance + code bytes) into C-only source-generated nodes, never compared (commands/manage_autouid_command.py:34-49, 282-338): a formula to borrow, not a mechanism to enable. The one hook, StrictDocPlugin.traceability_index_build_finished (strictdoc/core/plugin.py:7-11), runs after every reader and only when the 12 s feature is on. In the repo, fp-check is one-directional by design: a PARENT_FP entry compares the PARENT's current contract_hash (dev/scripts/sdoc_fp.py:32-38; fp-check.py:54-78), so a node editing its own STATEMENT dirties nothing it holds; File relations are excluded from the fingerprint machinery in three places (sdoc_fp.py:91-97; fp-check.py:57-60; cycle-check.py:13,37); and RELATIONS is a STRUCTURAL_KEY, so nothing inside a relation enters any contract hash. The grid: docs/sdoc/board/grammar-groups.json:2 says its glosses are copied verbatim from NAR-CANON-TYPES-GRID, dev/scripts/grammar-groups-check.py:42-43 says it does not compare them with their sources, and NAR-CANON-TYPES-GRID cannot write a File relation at all because NARRATIVE declares none (docs/sdoc/grammar.sgra:284-296; packages/strictdoc-grammar/values.nix:298-303).

"Dirty at either end" is therefore a new notion with four parts, costed as the dirty-edge rows below: an edge that records both the owning narrative's own contract_hash (a notion fp-check lacks) and a code-side hash over the file bytes, a LINE_RANGE or a function byte range, dirty meaning either differs from current; storage in strictdoc's HASH slot, forcing a checker over sdoc_model.Graph because the export drops it, or in PARENT_FP under a path key, stretching DEC-FINGERPRINT-IN-NODE's "strictly downward" (docs/plans/strictdoc-tooling/dec-fingerprint-in-node.sdoc:12-19) and meeting the retirement condition it names; a signer beside fp-accept, the only PARENT_FP writer (fp-accept.py:60-77); and a scope-aware writer and argv, since _build_reference emits VALUE only and _find_relation keys File relations by path alone (sdoc_model.py:277-284, 338-346). Direction: the edge inside every rule is NAR-CANON-TYPES-GRID to File grammar-groups.json. The reverse, the render's MECHANISM depending on the narrative, is what the operator's phrasing implies and is forbidden two ways: "nothing in the grid may depend on one" (docs/spec/nar-semantic-layer-type-narrative.sdoc:18), and MECHANISM has no Cites role (grammar.sgra:75-94).

Recommendation. The cheapest grid-in-code with a dirty edge is entirely repo-side and needs no reader, no grammar package and no feature flag: give NARRATIVE rel.file and regenerate the grammar; fix the one-line scribe --role File defect (the since-fixed scribe File-role defect); point NAR-CANON-TYPES-GRID at grammar-groups.json, the copied prose rather than grammars.js, with a File relation whose HASH slot holds the narrative contract_hash plus a sha256 of the file or a LINE_RANGE, written by a signer beside fp-accept; add a Graph-based checker as a fifth runCommand in nix flake check; and make review the act of re-signing after an LLM or a human compares the two ends. Roughly one week, dominated by threading scope and hash through sdoc_model, scribe_ops and scribe argv, with the HASH-slot-versus-PARENT_FP storage choice the one decision to put to the operator first. Defer the native path: it adds link resolution and an HTML source view but no drift detection, costs about 11 s on every export and every CLI write, and turns unindexed files into false errors. Defer the Nix and TypeScript readers with it; the prototype proves the seam is open with zero package edits, and function-grained edges are the only thing they buy. When that grain is wanted, build the Nix reader first (ctypes route unless the ABI-13 floor moves), keep kinds as description overrides on function and class rather than forking the closed vocabulary, and only then choose between an in-process reader and a JSON-hydrating one fed by the existing ast-grep extractor.

| item | size | driver |
| --- | --- | --- |
| Enable REQUIREMENT_TO_SOURCE_TRACEABILITY in the repo (native path) | hours of config (three ProjectConfig keys plus skip_source_files), then a standing tax of about 11 s on every export and every CLI write against a budget of about 1 s | measured 12.32 s vs 1.52 s on 890 files, one error per run, binaries reported missing, and include_source_paths narrowing flips unlisted files into false positives because the predicate is "indexed", not "exists" (mech-file-relation-existence.sdoc:47-58; strictdoc/core/project_config.py:358-399, 894-932) |
| Package tree-sitter-nix into strictdoc's venv interpreter | 0.5-1 day, plus HM and devenv module parity if it ships as a module | no site-packages output, so a makeWrapper PYTHONPATH wrapper like mkExtract.nix:89-98; ctypes on the grammar's parser library (zero deps, a DeprecationWarning) or the nixpkgs binding with four extra deps; ABI 13 sits on py-tree-sitter 0.25.2's compatibility floor (scratch probe_grammars.py) |
| Nix reader, prototype to production | 77 lines exist and run end-to-end; 200-300 lines mirroring reader_c.py plus 300-600 lines of tests: 2-4 days | comment attachment (a set's first binding hangs off binding_set.prev_sibling, handled at scratch e2e/strictdoc_config.py:49), let, rec, inherit and formals scoping, mkOption and mkEnableOption detection to label option vs module vs function, custom_tags; lands in the repo's strictdoc_config.py with zero package edits (reader_c.py:81-456; reader_python.py:69-217) |
| TypeScript reader (interface, type alias, class, function, enum, namespace, method) | 150-250 lines plus tests: 1-3 days | export_statement unwrapping, a name field per inner node, method_definition in class_body, a leading comment as prev_sibling of the export_statement, and a .ts vs .tsx branch like reader_c.py:100-103 |
| First-class kinds beyond function and class (module, option, interface, type as ELEMENT or scope words) | about seven core edits, 1-2 days, plus a patch carried in overlays/dev-tools/strictdoc.nix indefinitely or an upstream PR of unknown acceptance; 0 hours via description override | closed vocabulary in marker_lexer.py:39, marker_parser.py:206-226, language_item_marker.py:13-16, reference.py:78-87, file_traceability_index.py:634-661 and 975-980, markdown/reader.py:1906-1922, sdoc/writer.py:545-549; no extension guide upstream; #2214 unanswered since 2025-05 |
| JSON-hydrating reader for the ast-grep extractor | 40-80 line reader plus a JSON contract on the extractor side: about 1 day | no ingest API; runs inside strictdoc's process per export; the pickle cache is keyed to the source file, so changed extractor output is invisible until out/_cache is removed, and no CLI flag busts it (pickle_cache.py:26-77, 104-140) |
| Dirty edge, step 1: rel.file on NARRATIVE | 2-4 hours | NARRATIVE declares only Cites, Contains, Backlogged_In and Over, so scribe relate fails on the grammar before any tooling is reached (grammar.sgra:284-296; values.nix:298-303); regenerate grammar.sgra and update the corpus check expectations (flake.nix:325) |
| Dirty edge, step 2: scope and hash on a File relation through writer and argv | 1-2 days | _build_reference emits VALUE only; sdoc_model relation construction, scribe_ops relation handling, and the scribe argv and wire shapes must each grow LINE_RANGE or ELEMENT plus ID, and HASH; _find_relation keys File relations by path alone, so a second scoped edge to one file is refused as a duplicate; strictdoc parses and format-round-trips every field, measured |
| Dirty edge, step 3: two-sided signature, signer and checker | 2-3 days | fp-check is parent-only and File-blind (sdoc_fp.py:22-38, 91-116; fp-check.py:54-78); the JSON export drops HASH, so the checker reads sdoc_model.Graph or the exporter is patched (json_generator.py:310-323); the signer sits beside fp-accept because PARENT_FP and HASH writes are guarded (fp-accept.py:54-77; scribe_ops.py:52-64); HASH slot vs PARENT_FP path key is an operator call (dec-fingerprint-in-node.sdoc:12-19) |
| Dirty edge, step 4: CI wiring and the review verb | hours for the check; 0.5-1 day for the review and re-sign loop; severity policy undecided | mirror checks/strictdoc-file-check.nix:43-46 and :63-64 with ${self} as root, the same local-vs-CI asymmetry file-check.py:90-98 has; review is a re-sign after a human or LLM compares the ends, hosted by traceability_index_build_finished only if the native feature is on; fail-vs-report left to the operator as in mech-plan-refs-check.sdoc:43,53 |
| Fix scribe relate --role File (the since-fixed scribe File-role defect) | 1 line plus a test: 1-2 hours | scribe_ops.py:147-153 passes the role verbatim where :203-206 maps File to the empty string; measured refusal against the live graph; two File relations on MECH-SDOC-BOARD-GRAMMARS-VIEW are missing because of it, and the dirty-edge work hits it on its first relate |
<<<
NOTES: >>>
Filed 2026-09-02 against strictdoc 0.28.3 (the dev shell's binary, /nix/store/9khac7sfda0rzk6blqd3cnlwb7q3hsvz-strictdoc) and this worktree at 2f90b224 on feat/strictdoc-trial; main at 4705317b has none of dev/scripts/sdoc_*, docs/sdoc or strictdoc_config.py. Four independent readers covered the package's registry and readers, its marker grammar and resolver, the repo's fingerprint and check tooling, and grammar packaging; their reports were reconciled into the STATEMENT, and every disagreement among them or with upstream prose is kept below rather than resolved.

Contradictions, all kept:

1. Direction of the dirty edge. The operator's phrasing ("dirties your edge to the hard coded grammar render in code") has the code-side node depending on the narrative; reader 3 holds that this reverse edge is ruled out by "nothing in the grid may depend on one" (docs/spec/nar-semantic-layer-type-narrative.sdoc:18) and by MECHANISM having no Cites role (docs/sdoc/grammar.sgra:75-94), and that the compliant shape is NARRATIVE to File with a two-sided signature on the edge. Both positions kept; the operator owns the call.

2. Where the code-side hash lives and who reads it. strictdoc's HASH slot on the relation (a checker over sdoc_model.Graph, since strictdoc/backend/json/json_generator.py:310-323 drops HASH, or a patched exporter) versus PARENT_FP with a path key (a File branch in fp-check plus a stretch of docs/plans/strictdoc-tooling/dec-fingerprint-in-node.sdoc:12-19, "fingerprints point strictly downward", whose RETIRES_ON names exactly "per-edge state a node field cannot carry"). Readers 1 and 2 confirm the export blindness but do not choose. Undecided.

3. Edge target for the grid: grammar-groups.json (the copied prose, reader 3's recommendation and the "content never in renderer" rule) versus grammars.js or index.html (where the existing MECH-SDOC-BOARD-GRAMMARS-VIEW File edges point, docs/sdoc/board/.sdoc/mech-sdoc-board-grammars-view.sdoc:52-55).

4. Cost of enabling the native feature. The repo node measured 12.32 s vs 1.52 s per export on 890 files and says narrowing include_source_paths produces false positives (docs/plans/strictdoc-tooling/mech-file-relation-existence.sdoc:47-58, 83-109); reader 1 lists the real cost of the scan on this repo as unmeasured under its lens, and the scratch prototype ran in 1.09 s on a two-file tree with include_source_paths narrowed to its src/ directory (scratch e2e/run1.log). The 12 s figure is the only whole-tree measurement; narrowing is measured only as a false-positive risk, not as a timing.

5. Which reader is the template. Reader 1: reader_python.py (391 lines) is the smallest; reader 2: reader_c.py (539) is the most complete for a node-walking reader because of comment adjacency, decl/def and custom_tags; reader 4: reader_rust.py (729, TS_QUERY-driven) is the "load the grammar and patterns" shape the operator described. A choice of starting point, not a factual conflict; the measured prototype is closest to the Python shape.

6. Upstream docs versus upstream code on classes. The user guide (l.3205-3206) says classes are traceable in Python, C++ and others; l.3237-3238, 3260 and 3443 say scope=class and CLASS: are Python only; release 0.4.0 said C++ class markers were not yet implemented, with no later reversal. Code: Reader_C.supported_elements() returns function and class (strictdoc/backend/sdoc_source_code/reader_c.py:82-84) and the resolver matches classes by display_name for any reader (core/file_traceability_index.py:975-980). Whether the C++ reader actually emits class-scoped items was not measured.

7. The user guide's "and others" language list (l.3198-3210; L2 SDOC-SRS-142 names Ada and Gherkin) versus the code's closed suffix chain of exactly .py, the C family, .robot and .rs (reader_registry.py:34-53). Ada (#2345) and JS/TS (#2214) are open requests; no reader exists.

8. The source-nodes heading "experimental, for C/C++ and Rust only" (user guide l.3531) versus release 0.22.0 adding Robot source nodes and the registry passing custom_tags to the Robot reader (reader_registry.py:46-48). Docs stale.

9. Inside the repo: packages/strictdoc-grammar/values/spec.nix:1-2, 32-34 says "NO FILE RELATIONS ANYWHERE, deliberately ... Declaring one would owe a staleness story on day one", but that file is a proposal, not wired; the live grammar (docs/sdoc/grammar.sgra:91, 142, 196, 344, 398) declares File on five types, and the staleness story is what is now being asked for.

10. Reader 4's unknown, whether the generic reader requires scope=file in the literal top comment, is answered by code: the textX grammar matches an @relation marker on any line (strictdoc/backend/sdoc_source_code/grammar.py:24-31) and reader 1 measured a scope=file marker in a .nix file resolving (scratch exp3b). The user guide's "must be added to the top comment" (l.3243) is stricter than the generic reader enforces; language-aware readers do enforce position by their own adjacency rules.

11. Staleness of MECH-NODE-CODE-LINKAGE-IS-PROSE: docs/plans/strictdoc-tooling/mech-node-code-linkage-is-prose.sdoc:13 says 3 File relations on 2 nodes in a 144-node graph; the tree at 2f90b224 has 49 on 35 nodes across 432 nodes (measured: git ls-files '*.sdoc' piped through grep for the File TYPE line). Both figures kept; the node is dated 2026-08-27 and the growth landed after it.

12. Role-validation asymmetry (reader 1 only, from code): ForwardLanguageItemMarker inherits LanguageItemMarker and is skipped by the File-role check, while backward LineMarker and forward range and file markers are validated against the grammar's File ROLE declarations (strictdoc/core/file_traceability_index.py:1105-1127). Relevant if a role such as Implementation is put on a function-scoped marker; not contested by the other readers, not measured.

Unmeasured or unknown to the readers: the timing of a narrowed include_source_paths on this tree (item 4); whether the C++ reader emits class-scoped items (item 6); whether a backward @relation(NAR-CANON-TYPES-GRID, scope=file) marker inside a JSON $comment string parses under the generic reader, whose regex matches mid-line (grammar.py:24-31), which matters only if the native feature is on; which file the grid's edge should target (item 3); and the role-validation asymmetry's effect in practice (item 12).
<<<
