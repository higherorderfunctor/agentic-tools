[DOCUMENT]
TITLE: Deliver the board's elkjs layout engine through Nix

[GRAMMAR]
IMPORT_FROM_FILE: @repo

[WORK]
UID: WORK-BOARD-ELKJS-VIA-NIX
TITLE: Deliver the board's elkjs layout engine through Nix
AUTHORED_BY: llm
STATEMENT: >>>
The Graph neighborhood view ported on 2026-09-08 vendors the elkjs layout
engine under docs/sdoc/board/assets/vendor/elkjs/ (elk-api.js 9,782 bytes,
elk-worker.min.js 1,595,334 bytes, plus LICENSE and NOTICE), served by
docs/sdoc/board/server.py under two static routes. DEC-DEPS-VIA-NIX rules
that runtime dependencies enter through Nix, so the bundle should come from
a nixpkgs attribute or a pinned buildNpmPackage, with its store path handed
to the server by an environment variable set in devenv.nix the way the
tree-sitter grammars reach the extractor, and the vendored directory
removed. Until then the directory is excluded from treefmt, because biome
can neither fix the browserify-built elk-api.js nor read the worker above
its one-mebibyte limit; that exclude leaves with the vendored files.
<<<
NOTES: >>>
elkjs 0.12.0, from https://registry.npmjs.org/elkjs/-/elkjs-0.12.0.tgz, hash
sha256-wddxlyPgILEHJOPMvJNWlqKITx5402HN0DdmMJ6Ojio= out of nix store
prefetch-file.

Delivered by boardElkjs, a pkgs.runCommand declared in devenv.nix beside
grammarPython, NOT by an overlay under overlays/generic/. An overlay entry is a
published package of this flake: it lands in pkgs.ai.* and packages.<system>
and owes a config.checks.cacheHitParity row, a config.update.targets row or a
written updateTargetExempt reason, and -- being tracked against the npm
registry -- a sidecar plus an update script the 4x/day sweep runs. A browser
asset only the dev-only board loads earns none of that, and publishing elkjs as
a product of nix-agentic-tools would misstate what this repo ships.
grammarPython is the precedent for the shape chosen instead.

Store path /nix/store/b322wx755zcblzqaprl77x1wmn7p2iwq-elkjs-0.12.0, 7.8 MiB --
the whole npm package, of which the board serves two files out of lib/.

Byte-identity holds: lib/elk-api.js is sha256
ccca46175c05bbd280b5de6c9853103711e52c666a101f145b717e345363e24d and
lib/elk-worker.min.js is
e4f5c51c6f2fd564bb64e52e81c4a85a316ef2f24f8b90e1db5eb886c765b030, the same two
hashes the removed NOTICE.txt recorded for the vendored copies. Nothing the
browser receives changed.

Delivery variable: devenv.nix sets SDOC_BOARD_ELKJS_DIR to the derivation lib
directory, in the same env block as the SDOC_TS_*_PARSER paths, so the dev
shell and the board process both carry it. server.py resolves it at import and
refuses to start when it is unset or the two files are missing, naming devenv
up board as the fix. The two route paths are unchanged, so index.html,
layout.js and test_board.py needed no edit; the treefmt exclude for the vendor
tree left with the files, and MECH-SDOC-BOARD-LAYOUT dropped the four File
relations that pointed into it.

Verified 2026-09-08: both asset routes 200 at their original byte counts (9,782
and 1,595,334), /?view=graph 200, 16 board tests OK, and formatting, repo-lints
and all 14 strictdoc-* checks green.
<<<
RELATIONS:
- TYPE: Parent
  VALUE: DEC-DEPS-VIA-NIX
  ROLE: Governed_By
- TYPE: Parent
  VALUE: MECH-DEBT-SHARED-UNDERSTANDING
  ROLE: Assumes
- TYPE: Parent
  VALUE: WORK-GRAPH-NEIGHBORHOOD-VIEW
  ROLE: Assumes
- TYPE: Parent
  VALUE: MECH-BACKLOG-SHARED-UNDERSTANDING
  ROLE: Backlogged_In
