[DOCUMENT]
TITLE: Replace the transitions engine with a standard-library interpreter over the model document

[GRAMMAR]
IMPORT_FROM_FILE: @repo

[WORK]
UID: WORK-SEMANTICS-STDLIB-INTERPRETER
TITLE: Replace the transitions engine with a standard-library interpreter over the model document
AUTHORED_BY: llm
STATEMENT: >>>
Rewrite dev/scripts/sdoc_semantics/engine.py as a standard-library-only
interpreter over model.json and take the payload contract to
sdoc-semantics/2. What it does, in order:

1. Load and validate. Refuse a document whose schema string is unknown, whose
   operation names fall outside the closed table, whose state, gate,
   lifecycle, actor, checkpoint or transition references do not resolve, or
   whose lifecycle subject names a field or role the grammar does not declare
   (the grammar cross-check the spike already does). Errors name the
   vocabulary the document does declare.
2. Predicates. A closed table of operations over a node, its relations and
   the acting context: field_is, field_at_least (by ladder rank),
   has_relation (role, direction, optional target type), all_related and
   any_related (role, predicate, and what an empty set means: pass or fail),
   actor_in, and, or, not. About ten. Traversal is one hop; depth-bounded
   selection stays out until an instance rule needs it. A new operation
   is a small addition to the table with its own positive and negative test; a
   rule that fits an existing one is data only.
3. Dispatch. fire(graph, command, actor) preflights every gate on the
   transition, applies the write to a STAGED copy of the graph, collects the
   emitted events, ripples them through every lifecycle whose transitions
   listen (deterministic order: lifecycle order in the document, then subject
   uid), with a visited set and a step bound so a cyclic model refuses instead
   of hanging, then commits the staged copy in one step or refuses the whole
   change naming the gate or the bound that refused. The original graph is
   untouched on refusal. Every ripple step is recorded with its provenance:
   the subject moved, the transition taken, the event that caused it, the
   subject that emitted that event, and the gate or rule that let it through.
   fire() returns that log with its verdict, so the board can later show why
   an edge went dirty.
4. Relation contracts. check(graph) reports every edge whose role, source
   type or target type breaks a contract, and every cycle on a role that
   admits none.
5. Diagnostics over the document alone: unreachable state, no initial, no
   terminal, ambiguous dispatch, grammar vocabulary mismatch. The existing
   positive controls carry over.
6. Rendering: a mermaid stateDiagram-v2 emitter with safe state identifiers
   (state names carry dashes), one diagram per lifecycle, gate names on the
   edges.
7. Payload sdoc-semantics/2: everything v1 carries, plus gates,
   relation_contracts, actors, commands, events, operations, milestones,
   checkpoints, flows, and the
   derived gate placement (which checkpoints a gate may run at, from what each
   sees). by_type stays. The board (docs/sdoc/board/source.py, the Rules
   section, fsm.js) reads v2, and its unavailable degrade path stays.

The graph the interpreter reads is an adapter over the daemon's loaded corpus
(dev/scripts/sdoc_model.py), never a second parser. Nothing enforces on write
yet: the daemon does not call fire() in this item, so the operator's shaping
starts from a document with no gates and a writer that still accepts every
move.

Tests: every operation with a positive and a negative control; transaction
refusal leaves the graph unchanged; a cyclic fixture is refused by the bound;
load validation rejects a bogus operation and an unknown state name;
presentation order survives (never alphabetised); payload v2 keys are exact;
mermaid identifiers are safe; and the three shipped lifecycles produce exactly
the payload rows they produce today. Fixtures that exercise gates, ripple,
contracts and flows live under the tests only; the committed model.json gains
no gate.
<<<
NOTES: >>>
Measurements this design leans on, from EV-SEMANTICS-ENGINE-ALTERNATIVES: a
standard-library interpreter covered every rubric row in 318 lines over a
250-line document; load and dispatch under a millisecond in-process; the
baseline's probe found an unreachable-state bug and a ripple that ignored one
event kind, both by negative controls.

Design calls made here, open to the operator: per-write gating in the daemon
rather than checkpoint-only, because scribe is the only writer; the write side
of a ripple is the interpreter's and rolls back as a whole; termination is
enforced by the interpreter, not assumed of the model; the board consumes the
same payload as the daemon.

Implemented 2026-09-03 (commit pending). The executable suite passes 32
contracts: positive and negative controls for all 9 closed predicate
operations; all 5 model diagnostics with failing fixtures beside the silent
shipped model; reference refusal; transactional gate refusal; deterministic
ripple provenance and cyclic-bound refusal; relation contracts; derived gate
placement; flow data; presentation order; exact v2 keys; safe Mermaid ids; an
isolated-Python CLI import; and exact equality of all 3 shipped machine rows to
the recorded sdoc-semantics/1 baseline. The board serves sdoc-semantics/2 on
127.0.0.1:8766 with no unavailable marker. Comparing the three readable
listings before and after has zero changed lines below the schema header; that
header alone moves from sdoc-semantics/1 to sdoc-semantics/2. The daemon remains
an observer: no write path calls fire().

Follow-up 2026-09-08: 41 semantics contracts pass under plain python3.
With a step bound of 24, the two-transition cycle previously logged 24 steps;
it now logs start, forward and back, then refuses the first repeated forward
transition (3 steps), leaving the graph unchanged. The step bound remains a
separate backstop. Relation diagnostics now return one deterministic cycle
witness per role with an explicit scan bound, as requested in the follow-up.
An isolated copy without sdoc_semantics imports scribe_cmd and accepts --help
for all 9 non-semantics verbs; the semantics verb reports unavailable.
STATUS and AUTHORED_BY still differ from the base only in the schema
header. Rule ownership is explicit data, edge subject identities are stable,
and every provenance step carries the same keys with a gate-name list.
<<<
RELATIONS:
- TYPE: Parent
  VALUE: DEC-SEMANTICS-MODEL-IS-DATA
  ROLE: Governed_By
- TYPE: Parent
  VALUE: WORK-SEMANTICS-MODEL-AS-DATA
  ROLE: Assumes
- TYPE: Parent
  VALUE: WORK-REVISIT-SEMANTICS-ENGINE
  ROLE: Assumes
- TYPE: Parent
  VALUE: MECH-SEMANTICS-DEFINITION-BOUNDARY
  ROLE: Crosses
