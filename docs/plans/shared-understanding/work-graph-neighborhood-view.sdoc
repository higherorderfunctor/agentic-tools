[DOCUMENT]
TITLE: Graph tab: pick a node from a list, draw only its neighborhood

[GRAMMAR]
IMPORT_FROM_FILE: @repo

[WORK]
UID: WORK-GRAPH-NEIGHBORHOOD-VIEW
TITLE: Graph tab: pick a node from a list, draw only its neighborhood
AUTHORED_BY: llm
STATEMENT: >>>
The Graph tab has a left pane listing every WORK node, searchable and filtered
by payload-derived work state. Selecting a work item carries its UID in the URL
hash and renders only its bounded neighborhood, never the whole canon. The
middle canvas defaults to one hop and exposes always-visible one-, two-, and
three-hop controls with a 48-node ceiling. Node-type filters and relation
filters scoped by source node type constrain traversal. Selecting a node within
the rendered graph fills the right-pane details without changing the focal work
item or hash.

A vendored ELK.js worker places cards and routes orthogonal edges with measured
label spacing; repeated same-role fan-outs share labels and genuinely shared
segments render once. Same-role route pieces that meet across an invisible ELK
junction are bridged only when they share semantic relations, preventing tiny
visible gaps without joining unrelated lines. Solid relation hues identify
payload-derived role names, while arrowheads preserve declared
source-to-target direction.

Graph cards host the same native HTML summary button as navigation, preserving
UID, state, title, source path, padding, and typography. SVG layers behind it
paint an outward blurred semantic silhouette, a full rounded node-type plate,
and a borderless main surface inset to reveal a stable three-pixel type tab.
No-fill perimeters span the full card above the transparent HTML contents: a
thin subtle-dark line is always visible, hover changes only a thicker line to
the node-type color, and semantic states change that line and enable the glow.
The body and tab geometry and fills never change between those states. Filters,
centered Hops, and zoom out, zoom in, and Fit share the header. A grouped,
bottom-aligned key explains encodings without covering graph controls.
<<<
NOTES: >>>
Operator, 2026-09-02, verbatim: "graph, add new left pane that's a list of
all nodes. search/filterable. selecting a node renders the graph and
immediate neighbors only. no more whole canon in graph. selecting in graph
gives right pane details. default to central node has highlighted picking
from left."

Reference implementation, 2026-09-02: the operator narrowed the left pane to
WORK items and requested a beadboard-like three-pane layout, orthogonal lines,
one/two/three-hop expansion, and node/edge-role filters. Relation-role controls
were subsequently scoped under colored source-node-type groups; Shift-click
sets every same-named role to the clicked checkbox's resulting state. The
reference lives on feat/work-graph-neighborhood-reference for a separate porting
session to evaluate.

Ported 2026-09-08 onto feat/strictdoc-trial as commits adf8e8d1..5ee1cc63 over
base 3548b09d: the bounded neighborhood view, the loosened graph key spacing,
the overlapping-route coalescer, and the simplified visual semantics. The
reference had been built against a board with no Grammars tab, no lifecycle
widget and no sdoc-semantics/2 payload, so its edits to the settled board nodes
arrived describing a smaller app; that canon was reconciled with the merged
tree in the same session -- schema strings corrected, the shared card renderer
restored to MECH-SDOC-BOARD-CANVAS, the static route list and switcher count
brought up to date, and every smoke measurement taken on the reference branch
labelled with where it was taken. The statement's "vendored ELK.js worker" has
moved on once more: the engine now reaches the server through
SDOC_BOARD_ELKJS_DIR under WORK-BOARD-ELKJS-VIA-NIX, with the served bytes
unchanged.
<<<
RELATIONS:
- TYPE: Parent
  VALUE: WORK-BOARD-SHIFT
  ROLE: Assumes
- TYPE: Parent
  VALUE: MECH-SDOC-BOARD-SCOPED-RELATION-FILTERS
  ROLE: Crosses
- TYPE: Child
  VALUE: EV-SDOC-BOARD-SCOPED-RELATION-FILTER-SMOKE
  ROLE: Produces
- TYPE: Parent
  VALUE: MECH-SDOC-BOARD-RELATION-ROLE-STYLES
  ROLE: Crosses
- TYPE: Child
  VALUE: EV-SDOC-BOARD-LAYOUT-LIBRARY-ASSESSMENT
  ROLE: Produces
- TYPE: Parent
  VALUE: MECH-SDOC-BOARD-GRAPH-CONTROLS-AND-KEY
  ROLE: Crosses
- TYPE: Child
  VALUE: EV-SDOC-BOARD-ELK-NEIGHBORHOOD-SMOKE
  ROLE: Produces
- TYPE: Child
  VALUE: EV-SDOC-BOARD-GRAPH-KEY-AND-ROLE-STYLE-SMOKE
  ROLE: Produces
- TYPE: Parent
  VALUE: MECH-SDOC-BOARD-CARD-OUTLINE-STATES
  ROLE: Crosses
