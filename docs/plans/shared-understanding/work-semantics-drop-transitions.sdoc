[DOCUMENT]
TITLE: Remove transitions from both Nix delivery sites

[GRAMMAR]
IMPORT_FROM_FILE: @repo

[WORK]
UID: WORK-SEMANTICS-DROP-TRANSITIONS
TITLE: Remove transitions from both Nix delivery sites
AUTHORED_BY: llm
STATEMENT: >>>
Remove ps.transitions from grammarPython in devenv.nix and
pkgs.python3Packages.transitions from pythonPathPackages in
packages/strictdoc-grammar/lib/mkExtract.nix, together with that wrapper's
install-check imports of transitions and MarkupMachine. After this item scribe
semantics, the strictdoc-semantics check and the board import nothing outside
the standard library for semantics, and the install check imports the
interpreter instead.

Record the closure change in NOTES when it lands: the nixpkgs transitions
package propagates pygraphviz unconditionally, 312 MB at each site measured on
2026-09-03, for a backend the engine never imported.

The daemon and the board need devenv processes down and then up after the
devenv.nix change; restart keeps the old environment.
<<<
NOTES: >>>
Ordered last of the three: the interpreter must be green under the old
environment before the dependency goes, so a failure is attributable.

Implemented and measured 2026-09-03 (commit pending), after the 32-contract
interpreter suite and strictdoc-semantics check passed under the old
environment.

- grammarPython: 357,486,880 bytes before
  (/nix/store/dc5wkfiaald1wr4fayymylv7805ivrzc-python3-3.14.7-env),
  265,083,120 bytes after
  (/nix/store/d5x04gv12zvaz9nqax3ns12wk4d0hk8i-python3-3.14.7-env):
  -92,403,760 bytes (-88.12 MiB).
- strictdocGrammarExtract: 1,020,635,152 bytes before
  (/nix/store/i4irxk8h3057261bw5nr6w3pvznli4lp-strictdoc-grammar-extract-0.1.0),
  928,235,704 bytes after
  (/nix/store/nmq53qq1h2m83r8dycy0bq660f4lkk0i-strictdoc-grammar-extract-0.1.0):
  -92,399,448 bytes (-88.12 MiB).

Each number is `nix path-info -S` on the named realized path. Recursive path
inspection finds neither transitions nor pygraphviz in either after closure;
`nix why-depends` against both former store paths reports no dependency. The
daemon and board were taken down and brought up on the new environment; the
board again serves sdoc-semantics/2 without its unavailable marker.

Follow-up 2026-09-08: the after path above now names the measured wrapper
with the install-check input restricted to sdoc_semantics; tests and
__pycache__ directories and all unrelated dev scripts are excluded. Later
interpreter edits can change the store path without changing its closure size.

Final follow-up measurement 2026-09-08: the after path above is the realized
wrapper from the final interpreter source, measured with nix path-info -S at
928,235,704 bytes. The install-check input is now a fileset of interpreter
Python files and model.json, excluding tests, documentation, bytecode and
empty directories; the earlier path filter retained an ignored empty machines
directory in direct worktree evaluation.
<<<
RELATIONS:
- TYPE: Parent
  VALUE: DEC-SEMANTICS-MODEL-IS-DATA
  ROLE: Governed_By
- TYPE: Parent
  VALUE: DEC-DEPS-VIA-NIX
  ROLE: Governed_By
- TYPE: Parent
  VALUE: WORK-SEMANTICS-STDLIB-INTERPRETER
  ROLE: Assumes
- TYPE: Parent
  VALUE: WORK-REVISIT-SEMANTICS-ENGINE
  ROLE: Assumes
