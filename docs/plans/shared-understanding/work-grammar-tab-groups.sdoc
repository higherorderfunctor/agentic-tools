[DOCUMENT]
TITLE: Group the Grammars tab for reasoning, guarded by a coverage check

[GRAMMAR]
IMPORT_FROM_FILE: @repo

[WORK]
UID: WORK-GRAMMAR-TAB-GROUPS
TITLE: Group the Grammars tab for reasoning, guarded by a coverage check
AUTHORED_BY: llm
STATEMENT: >>>
Group the Grammars tab by a hand-authored layout file, grammar-groups.json,
that places the grammar's node types into sections and groups for reasoning.
Section Spec holds group Definition, drawn as a 2x2 grid of the definition
family on the two axes DEC-NODE-FAMILIES rules (normative vs descriptive,
universal vs particular: REQUIREMENT normative/universal, DECISION
normative/particular, MECHANISM descriptive/universal, EVIDENCE
descriptive/particular), and group Coverage, holding
USE_CASE. Section Unsorted holds every remaining type until the operator
organizes them; its purpose is to surface the grammar-file splits they may
want (WORK-GRAMMAR-FILE-SPLIT). Two guards make the hand-authored file an
allowed exception to REQ-BOARD-GRAMMAR-DRIVEN rather than a violation: a
static check in nix flake check that every grammar node type is placed
exactly once or falls into the one catch-all, and that no placed type is
stale; and a runtime check on the page that shows a loud red banner for a
missing or stale type and never hides a type. Visually, each section is a
top-level heading followed by a horizontal rule, each group a subtitle, and
under it the cards centered or the 2x2 grid as a custom widget. The
Perspective pill moves to the end of the view switcher.
<<<
NOTES: >>>
Operator, 2026-09-02, verbatim: "I want groups, to start to help surface
the splits I may want.
# Spec
## Definition
2x2 Grid
## Coverage
- Use Case
# Unsorted
Rest of em till I organize
Given the current design consider good way to visualize, like
# TOP
<HR>
## Sub-title
<center the cards or the grid for custom widget>
something like that. while in there move perspective tab to be last not
first."

Landed 2026-09-02: 8823edf1 (the tab and the check), 35f2a499 (the pill
order); static check strictdoc-board-grammar-groups in nix flake check;
runtime banner; verified by an independent agent (headless chromium +
positive controls on the check).

Axis words corrected 2026-09-02 to DEC-NODE-FAMILIES' universal/particular;
the carver had written all/one from a summary table.

Operator, 2026-09-02, verbatim, on the grid becoming code with a dirty edge: "so hard coding the grid becomes like @relation(REQ-1, scope=file) pointed to NAR-CANON-TYPES-GRID. If the narrative changes it dirties your edge to the hard coded grammar render in code forcing a review (ideally LLM). this is a core feature of canon we just haven't built out yet." The buildout is WORK-CODE-LINKAGE-EXTRACTORS, with the assessment in EV-STRICTDOC-SOURCE-TRACEABILITY-LOE. Option 1 (render the grid from the narrative) versus option 2 (keep the grid in code and hang a dirty edge on it) is still the operator's open call.
<<<
RELATIONS:
- TYPE: Parent
  VALUE: WORK-BOARD-SHIFT
  ROLE: Assumes
