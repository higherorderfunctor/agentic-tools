[DOCUMENT]
TITLE: Cycle detection over the JSON export

[GRAMMAR]
IMPORT_FROM_FILE: @repo

[MECHANISM]
UID: MECH-CYCLE-CHECK
TITLE: Cycle detection over the JSON export
AUTHORED_BY: llm
STATEMENT: >>>
Detect relation cycles in the exported graph independently of StrictDoc.
<<<
RATIONALE: >>>
StrictDoc's own cycle detection queries the graph without specifying an edge
role, and the graph database returns only the bucket of role-less edges. Every
relation in this grammar carries a role, so no cycle in this corpus is detected;
the failure surfaces as a recursion-depth crash during render.
<<<
NOTES: >>>
Implemented: dev/scripts/cycle-check.py, an iterative (non-recursive, so it
cannot hit the exact recursion-depth failure it replaces) DFS over every
Parent-type RELATIONS entry regardless of ROLE -- File relations excluded,
since their VALUE names a filesystem path, not a node. CI gate:
checks/strictdoc-cycle-check.nix, mirroring strictdoc-fp-check.nix's clean
$TMPDIR export harness (SLICE-FP-DETECTOR) rather than sharing its
derivation, so the two checks stay independently attributable on failure.

Verified past the happy path with two synthetic fixtures, not just the real
graph: a 3-node cycle where every edge carries a role (A --Assumes--> B
--Assumes--> C --Assumes--> A) is caught and reported with its role chain,
plus a disjoint acyclic pair in the same export to prove no cross-node false
positive; and an acyclic diamond (two paths converging on one node) plus a
File relation whose VALUE equals its own owning node's UID, to prove that
is not mistaken for a self-loop. Real graph: 61 nodes, 36 role-carrying
edges, 0 cycles found.

Positive control re-run independently at review, against the real graph rather than a fixture: a role-carrying two-cycle was injected by closing a loop back against an existing Governed_By edge. strictdoc export exited 0 and reported nothing; cycle-check exited 1 and named the path. The role-blind premise is therefore measured here, not inherited.
<<<
