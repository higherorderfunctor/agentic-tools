[DOCUMENT]
TITLE: The semantic-layer render is generated by scripts that live outside the repository

[GRAMMAR]
IMPORT_FROM_FILE: @repo

[EVIDENCE]
UID: MECH-RENDER-GENERATOR-OUTSIDE-REPO
TITLE: The semantic-layer render is generated by scripts that live outside the repository
AUTHORED_BY: llm
STATEMENT: >>>
The HTML artifact that SLICE-SEMANTIC-LAYER-RENDER asked for was built on
2026-08-29 by a four-step pipeline that lives only in the rendering session's
scratchpad: (1) a strictdoc export to JSON; (2) a parser over
MECH-SEMANTIC-LAYER-WHITEBOARD's STATEMENT that splits it into sections, tagged
lines and cited UIDs; (3) a hand-authored layer -- one plain-language headline
per line, a node-type assignment and a top-gap assignment per line, seven type
descriptions, five gap rewrites and a glossary; (4) a template that embeds the
merged JSON and renders every screen client-side.

None of that is in the repository. So the render cannot be regenerated after
the sheet is re-cut or a decision lands, and the hand-authored layer -- which
is where the translation judgement sits -- has no home and no review path.

Options, unweighed: commit the generator under docs/sdoc/ beside render.py and
keep the authored layer as data; treat the render as a one-off and re-author
it next time; or carry the plain-language headline in the canon as a field,
which is a grammar question and not this node's to answer.
<<<
NOTES: >>>
Filed by the rendering session, 2026-08-29. Measured while building: 145
tagged lines plus the five top gaps; the sheet's own tag counts (45 works, 17
fall out, 20 unaddressed, 18 open, 45 gaps) reproduce exactly from the parse;
59 UIDs cited, 95 nodes on the page once one-hop neighbours are included;
every cited UID resolved against the export at bbcc0060. One tooling trap:
Python's glob skips dotted directories, so a walker over the corpus misses
packages/*/.sdoc/ unless it uses os.walk -- caught while mapping UIDs to files.

Retyped from MECHANISM to EVIDENCE on 2026-08-30 by the mechanism mood test under DEC-NODE-FAMILIES, with medium confidence after a second opinion: it records what was observed once, not how something always behaves. Noted for a later split: The four-step pipeline paragraph is an architecture that becomes a MECHANISM the day the generator is committed under docs/sdoc/; 'Options, unweighed' is an open decision, not a claim. The UID keeps its prefix: DEC-UID-OUTLIVES-TYPE.

Delivery review retained when the completed render WORK row was retired on 2026-09-10. Five independent readers raised 37 findings: 23 were confirmed and fixed, 6 were split and resolved by falling back to the source sheet wording, 4 were refuted, and 4 nits were fixed. Phone and desktop screenshot passes found three layout defects before review, and all five tag colours passed the colour-vision validator in both themes.
<<<
RELATIONS:
- TYPE: Parent
  VALUE: MECH-BACKLOG-STRICTDOC-TOOLING
  ROLE: Backlogged_In
