[DOCUMENT]
TITLE: Retire PARENT_FP entries whose parent or relation is gone

[GRAMMAR]
IMPORT_FROM_FILE: @repo

[MECHANISM]
UID: MECH-FP-ENTRY-RETIREMENT
TITLE: Retire PARENT_FP entries whose parent or relation is gone
AUTHORED_BY: llm
STATEMENT: >>>
fp-accept rewrites a node's whole PARENT_FP field from a merge of the existing entries and the newly signed ones, and never removes anything: `dev/scripts/fp-accept.py:71` reads the existing entries into a dict and `:82` only ever assigns into it. An entry whose parent has been deleted, or whose backing relation has been dropped, is therefore carried forward on every subsequent sign. `MECH-FP-RELATION-LINT` detects both cases as fp-check's deleted and unbacked findings, so they fail the gate and stay failing until someone hand-edits the field — which the skill's third hard rule forbids. The writer needs a retirement path: drop an entry whose parent is absent from the export, and drop one with no backing Parent relation, in the same write that signs the rest, reporting each removal.
<<<
RATIONALE: >>>
Spun out of `MECH-SIGNATURE-REVOCATION`, whose sketch statement cited the retention as part of the revocation problem. It is a separate defect and must not be fixed with one rule: for a revoked entry, permanence is the property being bought, so any pruning must skip the revoked case explicitly. Without a retirement path the only way out of a failing gate is the edit the rules forbid, which is how a hard rule gets broken by someone with no other option.
<<<
NOTES: >>>
Inert today — 31 fingerprint entries, all the 0000000 placeholder, 0 suspect — and arms with the first real signature. `MECH-SIGNATURE-REVOCATION`'s NOTES already records the adjacent constraint from the other side: a revoked entry is not collectible lineage.
<<<
RELATIONS:
- TYPE: Parent
  VALUE: MECH-BACKLOG-STRICTDOC-TOOLING
  ROLE: Backlogged_In
