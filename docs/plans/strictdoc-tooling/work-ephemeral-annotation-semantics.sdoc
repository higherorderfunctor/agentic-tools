[DOCUMENT]
TITLE: Work out annotation that is not meant to last

[GRAMMAR]
IMPORT_FROM_FILE: @repo

[WORK]
UID: WORK-EPHEMERAL-ANNOTATION-SEMANTICS
TITLE: Work out annotation that is not meant to last
AUTHORED_BY: llm
STATEMENT: >>>
There is no way to annotate a node with something
NOT meant to survive to main. Comments, observed gaps, working notes, a
verdict left for the next session -- none of them are durable claims, and
today the only places to put them are NOTES on a real node or a new node that
outlives its usefulness. The corpus grows and nothing prunes it.

COMMENTARY exists as an element and nothing in the corpus is one; whether it
is the answer here, or whether ephemeral annotation is a different thing
again, is part of the question rather than the answer to it.

Not this session's to carry.
<<<
RELATIONS:
- TYPE: Parent
  VALUE: MECH-BACKLOG-STRICTDOC-TOOLING
  ROLE: Backlogged_In
