[DOCUMENT]
TITLE: File relations to nonexistent paths export clean

[GRAMMAR]
IMPORT_FROM_FILE: @repo

[MECHANISM]
UID: MECH-FILE-RELATION-EXISTENCE
TITLE: File relations to nonexistent paths export clean
AUTHORED_BY: llm
STATEMENT: >>>
Check every File relation against the repository tree in
dev/scripts/file-check.py, built in cycle-check.py's shape: it reuses
sdoc_fp's load_index and iter_nodes, prints every finding with its node UID
and owning document title, and exits non-zero when there is one. Its argv is
the export JSON plus the repository root, a second argument neither
cycle-check.py nor fp-check.py takes, because the JSON export carries no path
for anything and so offers nothing to resolve against.
checks/strictdoc-file-check.nix runs it over the flake source beside the
cycle and fingerprint checks, which puts it in nix flake check.

A VALUE is well-formed in exactly one shape: a normalized POSIX path relative
to the repository root, not absolute, with no leading ./ and no .. segment.
Any other shape is a finding in its own right rather than a path to normalize
and then resolve. The target must be an existing regular file; a directory is
a finding. That rule is upstream's, not ours -- strictdoc's own
file-traceability validation accepts precisely this shape and rejects ./x,
../x, an absolute path and a directory with the same message.

Upstream's validation is no longer hypothetical: source traceability was
turned on for this project on 2026-09-02, so strictdoc now applies that rule
itself at parse time. file-check.py stays beside it for two reasons rather
than out of caution. Upstream reports one broken relation per run, and the
checker reports every finding in one pass at 0.03 s. And the scribe daemon's
own graph load passes skip_source_files=True, so nothing upstream checks runs
on the path most writes actually take.

The scribe write path checks only the VALUEs it is about to write, applying the
same well-formedness rule plus one stat: microseconds, not a whole-graph pass.
scribe_ops.py normalizes each File target and the workspace precheck refuses a
write whose repository-relative target is missing, absolute, or carries a
forbidden dot segment. It also verifies the grain now, since a File relation
may name an item rather than a whole file: an ELEMENT and ID pair is checked
against the items the configured extractor really finds in that file, and a
missing id is refused with the nearest names and the command that lists them.
scribe_verbs.do_check repeats the same normalization and existence rules over
every relation in the held graph. The corpus-wide gate stays alongside both,
because a write-time check cannot see a file deleted or moved after its
relation was written, and that is the direction the ghost problem actually
runs. dev/scripts/element-check.py is the corpus-wide half of the grain check
and runs as strictdoc-element-check in nix flake check.

Two exclusions, both deliberate and both cheap to reverse. Targets outside
the repository are not supported; no File relation names one today. Forward
references are not supported either -- a node may not name a path its own
unbuilt work will create. The corpus carries 64 File relations on 37 nodes, 4 of
them element-grained and none using LINE_RANGE. Every target exists, so the
strict rule still costs nothing and relaxing it later is a one-line change,
where tightening it later would not be.
<<<
RATIONALE: >>>
This node's own earlier premise -- that the parser will not do it -- is
refuted. StrictDoc validates File relations exactly this way, but only when
REQUIREMENT_TO_SOURCE_TRACEABILITY is in project_features.

That feature was rejected on 2026-08-27 and turned ON on 2026-09-02, and the
thing that changed in between was the reader, not the appetite for the cost.
The rejection was measured: 12.32 s against 1.52 s on the 890-file tree, one
broken relation reported per run, and a predicate of "is an indexed source
file" rather than "exists", so a present-but-binary file read as missing. What
made it affordable was the operator's ruling that no generic parsing happens
at all. strictdoc's generic textX reader was 77% of a cold export, recompiling
its grammar once per file; with the reader registry replaced by a glob
manifest, every file outside the manifest gets a null reader. Measured on the
current 1397-file corpus: cold 9.3 s against 2.4 s off, warm 2.8 s against
2.1 s off, so about +0.6 s on every export. EV-STRICTDOC-EXPORT-TIMING records
it and `devenv tasks run strictdoc:bench` reproduces it.

A checker over the JSON export still has the exact predicate, reports every
finding in one pass, and costs 0.03 s, which is why it was kept rather than
retired when the feature came on.

The defect itself is worth closing rather than tolerating because a design
that claims code which no longer exists is the ghost problem the File role
was adopted to catch.
<<<
NOTES: >>>
Measured 2026-08-27 on a scratch copy of the tree, strictdoc 0.28.3
(/nix/store/cck3q51nd32dpbmpkwv5xpkxxhpnr2ak-strictdoc-env), every export
into a clean output directory.

The defect, and a positive control for the same harness:

- A File relation with VALUE packages/semble/lib/doesNotExist.nix exports
  with exit 0, emits no warning line at all, and the dead path survives
  verbatim into index.json.
- Replacing it with a dangling NODE relation fails the identical export with
  exit 1 and "references parent requirement which doesn't exist"
  (traceability_index_builder.py:663). The export gate is alive; it just does
  not cover File.
- Prototype checker over the JSON export: 0.03 s, exit 1, all three injected
  broken relations named in one run. Negative control on the unmodified
  corpus: 3 File relations checked, 0 broken, exit 0 -- both on the scratch
  copy and on the real graph.

Upstream's own check, measured by adding
project_features=["REQUIREMENT_TO_SOURCE_TRACEABILITY"] to the scratch
strictdoc_config.py:

- Broken path: exit 1, "Requirement MECH-FILE-RELATION-EXISTENCE references a
  file that does not exist" (file_traceability_index.py:615).
- Accepted forms, probed exhaustively: packages/semble/lib/withGrammars.nix
  passes, while ./packages/semble/lib/withGrammars.nix,
  packages/semble/lib/../lib/withGrammars.nix,
  ../../../packages/semble/lib/withGrammars.nix, /etc/hostname, the directory
  packages/semble, and a document-relative sibling filename such as
  mech-cycle-check.sdoc all fail.
  Resolution is a string lookup in the indexed-source-file map keyed by a
  POSIX path relative to source_root_path -- not filesystem resolution --
  which is why every non-normalized form fails while naming a real file.
- A file that exists but is not indexed reports the same "does not exist":
  measured on a .pyc and on a file containing a NUL byte, both skipped as
  binary. A plain .txt passes.
- Cost on the whole repo, 890 tracked files and 885 source tasks: 1.52 s off,
  12.32 s on, 244 MB maxrss. Narrowing include_source_paths to
  packages/semble/** drops it to 1.84 s and 16 tasks, but then
  dev/scripts/cycle-check.py -- which exists -- is reported as not existing.
  Narrowing trades cost for false positives and is not viable.
- One error per run: three broken relations across two nodes produced one
  error line, and it named the second node's.
- The JSON export is byte-identical with the feature on and off, so enabling
  it would not perturb cycle-check or fp-check.

Two traps found while measuring, neither confined to this node:

- ProjectConfig(project_features=[...]) REPLACES the defaults (TABLE_SCREEN,
  TRACEABILITY_SCREEN, DEEP_TRACEABILITY_SCREEN, SEARCH) rather than adding
  to them. The JSON export is unaffected -- measured identical -- but the
  HTML screens would be lost.
- StrictDoc's own grammar source calls this role experimental: "FileReference
  is an early, experimental feature. Do not use yet."
  (backend/sdoc/grammar/type_system.py:25).

The check's repository-root argument comes from the flake source in the check
derivation, following checks/strictdoc-cycle-check.nix's
"strictdoc export ${self}". That is the git-tracked tree, so a File relation
naming an untracked file passes locally and fails in CI -- correct behaviour,
but the failure appears at a distance from the edit.

sdoc_fp.iter_nodes walks only each document's top-level NODES and does not
recurse into sections. A recursive walk found the same 3 File relations on
that day's corpus, so the two were equivalent then; use iter_nodes for
consistency with the other two checkers and fix it in one place if sections
ever nest nodes.

IMPLEMENTED 2026-08-27 as dev/scripts/file-check.py, wired into nix flake
check by checks/strictdoc-file-check.nix. Built in cycle-check.py's shape as
specified, reusing sdoc_fp's iter_nodes and load_index and taking the
repository root as a second argument.

The write-time half now enters through scribe_ops.py and the workspace precheck: normalization plus an existence check refuse an absolute path, a dot segment, a parent segment, or a nonexistent target.

Positive control rather than a clean run reported as proof: against the real
corpus the checker reports 3 File relations and 0 findings, and against an
export with two VALUEs rewritten -- one to a deleted path, one to
'./packages/semble' -- it reports both and exits 1.
Updated 2026-09-03 for commits c64a0147, 7d6886d1 and 66f73b03. Three claims
above were true when measured and are false now, and each is corrected in
place rather than deleted:

- REQUIREMENT_TO_SOURCE_TRACEABILITY is ON. strictdoc_config.py sets it, and
  the reader registry is REPLACED rather than extended: dev/scripts/
  sdoc_extractors/registry.py's SOURCE_EXTRACTORS is the whole manifest, and
  every path it does not claim gets a NullSourceReader. No internal strictdoc
  reader is ever reached, .py and .rs included.
- The cost is 9.3 s cold and 2.8 s warm against 2.4 s and 2.1 s with the
  feature off, not the 12.32 s the rejection was argued on. The globs decide
  what is PARSED, never what is INDEXED, so every file still enters the index
  and a whole-file relation to any path still resolves. Narrowing
  include_source_paths instead would break exactly those relations.
- "All three File relations in the corpus" is now 64 on 37 nodes, 4 of them
  element-grained. The upstream-accepted-forms probe below still holds; only
  the counts and the on/off state moved.

The scribe File-role write defect was fixed in 6fbaa76b and its completed WORK row retired on 2026-09-10. relation_role in dev/scripts/sdoc_model.py centralizes the client spelling File to the grammar's empty role; _relation_spec in dev/scripts/scribe_ops.py now serves relate, unrelate, and new alike. test_file_relation_names_an_item exercises the typed-operation path. MECH-SDOC-BOARD-GRAMMARS-VIEW now carries File relations to both grammar-groups.json and its static checker.
<<<
RELATIONS:
- TYPE: File
  VALUE: dev/scripts/file-check.py
- TYPE: File
  VALUE: dev/scripts/element-check.py
- TYPE: File
  VALUE: strictdoc_config.py
