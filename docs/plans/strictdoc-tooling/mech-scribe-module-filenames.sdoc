[DOCUMENT]
TITLE: The writer's module files still carry the retired name

[GRAMMAR]
IMPORT_FROM_FILE: @repo

[MECHANISM]
UID: MECH-SCRIBE-MODULE-FILENAMES
TITLE: The writer's module files still carry the retired name
DEPTH: sketch
AUTHORED_BY: llm
STATEMENT: >>>
The writer command is scribe and its module names now expose the actual layers. scribe_cmd.py owns argv and the grammar-derived option surface, scribe_ops.py owns typed daemon operations, scribe_workspace.py owns the resident graph, and scribe_verbs.py owns only shared rendering and path helpers. The verbs module has no parser, dispatch table, main function, or executable entrypoint, so the source tree no longer advertises a second writer.
<<<
RELATIONS:
- TYPE: Parent
  VALUE: MECH-BACKLOG-STRICTDOC-TOOLING
  ROLE: Backlogged_In
