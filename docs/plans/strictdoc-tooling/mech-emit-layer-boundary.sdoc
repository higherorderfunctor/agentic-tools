[DOCUMENT]
TITLE: Emit is the renderer composed with the type mapping, and they split cleanly

[GRAMMAR]
IMPORT_FROM_FILE: @repo

[MECHANISM]
UID: MECH-EMIT-LAYER-BOUNDARY
TITLE: Emit is the renderer composed with the type mapping, and they split cleanly
AUTHORED_BY: llm
STATEMENT: >>>
Settled with the operator 2026-08-26. Two jobs, one composition:

  the inner emitter -- takes values that are all strings, knows the FILE FORMAT,
    and does no encoding. A pure renderer.
  denormalize      -- knows the TYPE MAPPING: a Nix bool becomes the literal
    True or False, an enum member becomes its bare string, a list becomes a
    comma-space join.
  the outer emitter = the inner one composed with denormalize.

The normalized surface is deliberately a MIXTURE, and this is already how it is
built: a shape no converter upgraded stays as the extracted string, carried
inside normalized rather than pushed elsewhere. regexPreserved records that as
"unchanged" with a null encoder, and the current file has four upgraded sites
sitting beside five that stayed patterns. So a consumer never falls off the
normalized surface -- the untranslated case surfaces there in its original
form.

The inner emitter therefore has a real caller: someone holding string values
who is deliberately skipping the type layer, which is the same role `raw` plays
one level up. It is not an escape hatch for cases the surface cannot express.

Mechanism, if the two are exposed from one value: an attrset carrying
__functor is callable AND openable, so `emit xs` and `emit.<inner> ys` both
work with no module system and no override machinery. Measured.
<<<
RATIONALE: >>>
Recorded because the shape was argued to the wrong conclusion twice before
landing here -- first as two code paths that would drift, which was wrong since
it is one implementation composed, then as an escape hatch for the
inexpressible, which was wrong because the untranslated case never leaves the
normalized surface in the first place.
<<<
NOTES: >>>
OPEN, and deliberately not decided here: what the inner entry point is called
and whether it is exposed at all yet. It cannot be called faithful -- see
MECH-FAITHFUL-IS-NOT-A-CONSUMER-WORD. A leading underscore reads as private
across Nix, which is the wrong signal for something supported. Since __functor
makes adding it a one-line change later, waiting for a caller costs nothing and
removing a published attribute costs more than adding one.

IMPLEMENTED 2026-08-27. `lib/denormalize.nix` carries the encode halves and
`lib/sgra.nix` the file format; `lib/emit.nix` is the two composed, one entry
point per node type, derived from the renderer's own attribute names. The
renderer takes no `normalized` at all, which is what makes "no encoding on this
side" checkable rather than asserted. Both surfaces still render
docs/sdoc/grammar.sgra and fixtures/foreign.sgra byte for byte, and the
emitter-alone arm of the surface-live check still accepts every case it is meant
to, so the split moved no rejection across the type boundary.

Two boundary calls the sketch did not settle, both decided by what each half can
SEE. The `", "`-joined choice vocabulary is already a string by the time the
renderer runs, so "at least one option" is checked in denormalize -- the last
layer holding the list -- while "this kind needs a vocabulary at all" stays in
the renderer. And the file's spelling of each field kind and relation type
(`String`, `Parent`) stays in the renderer beside the other format constants: it
is not an encoded value, it is what the discriminator is called in the file.

__functor was not needed. The inner emitter is four renderers, not one function,
so the callable-and-openable trick has nothing to apply to unless a single entry
point is later published. The naming question above is still open, and nothing
outside `lib/emit.nix` reaches either half.
<<<
