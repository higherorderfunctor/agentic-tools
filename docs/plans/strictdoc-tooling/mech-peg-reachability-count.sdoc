[DOCUMENT]
TITLE: Nineteen rules are reachable from DocumentGrammarWrapper, not twenty-five

[GRAMMAR]
IMPORT_FROM_FILE: @repo

[EVIDENCE]
UID: MECH-PEG-REACHABILITY-COUNT
TITLE: Nineteen rules are reachable from DocumentGrammarWrapper, not twenty-five
AUTHORED_BY: llm
STATEMENT: >>>
Measured on 0.28.3. Walking rule references out of the arpeggio parser tree,
unioned with _tx_inh_by for the two abstract rules, closes at NINETEEN rules
from DocumentGrammarWrapper: BooleanChoice, ChoiceOption, ChoiceOptionXs,
DocumentGrammar, DocumentGrammarWrapper, FieldName, GrammarElement,
GrammarElementField and its four concrete kinds, GrammarElementRelation and its
three concrete kinds, RequirementType, ReservedKeyword, SingleLineString.

The implementation brief says 25 of 43. The difference is the access path, not
the grammar: _tx_attrs reports an attribute's declared class, and for a value
that is an inline regex textx declares it STRING, which drags textx's
synthesized base types (STRING, ID, BOOL, INT, FLOAT, STRICTFLOAT, NUMBER,
OBJECT, BASETYPE) into a metamodel-side walk. None of them appears in the peg,
and none of them constrains anything a .sgra file can say.
<<<
RATIONALE: >>>
Both numbers are right about their own walk. Recorded so a later session
checking the surface for completeness against the brief's 25 does not go
looking for six missing rules that are not rules of this grammar.
<<<
NOTES: >>>
Retyped from MECHANISM to EVIDENCE on 2026-08-30 by the mechanism mood test under DEC-NODE-FAMILIES, with high confidence after a second opinion: it records what was observed once, not how something always behaves. The UID keeps its prefix: DEC-UID-OUTLIVES-TYPE.
<<<
RELATIONS:
- TYPE: Parent
  VALUE: MECH-BACKLOG-STRICTDOC-TOOLING
  ROLE: Backlogged_In
