[DOCUMENT]
TITLE: Mechanism mood

[GRAMMAR]
IMPORT_FROM_FILE: @repo

[NARRATIVE]
UID: NAR-MECHANISM-MOOD-REVIEW
TITLE: Mechanism mood
AUTHORED_BY: llm
WIDGET: prose
STATEMENT: >>>
Which mechanisms were rules or observations, and which are held for a
ruling. Every node born as a MECHANISM was sorted on 2026-08-30 by the
definition grid's test ([LINK: DEC-NODE-FAMILIES]): if the world did
something this node says it does not, would you fix the world -- a rule,
which can be violated -- or fix the node -- a description, which can only
be wrong? And does it speak of every case, or record one observation? Ten
classifiers sorted 135 nodes; a second opinion argued both sides of every
proposed retype. 27 were retyped in place, keeping their UIDs
([LINK: DEC-UID-OUTLIVES-TYPE]); 4 are held at low confidence for the
operator, each wanting a split into a rule and a design rather than a
retype; 104 stayed mechanisms. The ledger is
[LINK: EV-GRID-MIGRATION-LEDGER]. Nothing here is signed; a verdict is the
test's reading, recorded in each node's NOTES.
<<<
PARENT_FP: >>>
DEC-NODE-FAMILIES:0000000
DEC-UID-OUTLIVES-TYPE:0000000
<<<
RELATIONS:
- TYPE: Parent
  VALUE: DEC-NODE-FAMILIES
  ROLE: Cites
- TYPE: Parent
  VALUE: DEC-UID-OUTLIVES-TYPE
  ROLE: Cites
- TYPE: Child
  VALUE: NAR-MECHANISM-MOOD-REVIEW-LEGEND
  ROLE: Contains
- TYPE: Child
  VALUE: NAR-MECHANISM-MOOD-REVIEW-RETYPED
  ROLE: Contains
- TYPE: Child
  VALUE: NAR-MECHANISM-MOOD-REVIEW-HELD
  ROLE: Contains
- TYPE: Child
  VALUE: NAR-MECHANISM-MOOD-REVIEW-STAYED
  ROLE: Contains
