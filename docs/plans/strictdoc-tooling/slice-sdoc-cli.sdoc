[DOCUMENT]
TITLE: A command-line tool that is the only writer of sdoc files

[GRAMMAR]
IMPORT_FROM_FILE: @repo

[WORK]
UID: SLICE-SDOC-CLI
TITLE: A command-line tool that is the only writer of sdoc files
DEPTH: implemented
AUTHORED_BY: llm
STATEMENT: >>>
The scribe command is the only supported command surface for producing and editing sdoc documents. scribe_cmd.py obtains workspace.grammar from the resident daemon and derives one field flag per declaration, the declared choices, and the relation roles for the selected node type. No corpus or grammar file is loaded by the client.

Writing verbs are new, set, relate, unrelate, move, and delete. Reading verbs are show, list, and check. The client sends typed operations to scribe_ops.py, which validates against the daemon-held graph and writes canonical form through StrictDoc. Every writing verb accepts dry-run and exercises the same candidate validation without changing disk or held state. UIDs remain operator-chosen and prefix checked; guarded AUTHORED_BY and PARENT_FP fields have no option and are refused before transport.

scribe_verbs.py is a library containing only the shared show, list, check, target-path, and prefix behavior. It has no argparse parser, dispatch table, main function, or executable entrypoint. The daemon is the only corpus owner and there is no no-daemon validator.
<<<
RATIONALE: >>>
In the operator's words, the root failure is a model producing incorrect formats
with nothing validating the write; the tool takes the model's hands off the
files. Measured: creating a node in-process costs 0.35 s, validating the whole
graph 0.3 s, and strictdoc's node model writes any field in grammar order --
nothing here waits on the behaviour model.

Deriving the option surface from the grammar rather than hand-writing it is what
makes the milestone small. The five node types are genuinely asymmetric -- a
DECISION carries no DEPTH and no File relation, a SPIKE is the only type
carrying both a DEPTH and a STATUS with a different word list under the same
name, an INVARIANT cannot point at a file -- and that asymmetry is exactly what
gets hand-written wrong.
<<<
PARENT_FP: DEC-EXECUTABLE-RULES-ROADMAP:0000000
NOTES: >>>
Scope was settled by the operator on 2026-08-27: the grammar defines the option surface, the writer formats and validates, and semantic lifecycle policy belongs elsewhere. The first implementation combined the command and graph code in a standalone module. The daemon work split that implementation by responsibility: scribe_cmd.py owns argv, scribe_ops.py owns typed operations, scribe_workspace.py owns resident graph writes, and scribe_verbs.py holds the few shared renderers and path rules.

The grammar-derived asymmetry remains observable in help: types receive only their declared fields, choices, and roles. Prefix-to-type agreement remains enforced for new nodes. delete remains available but is deliberately not taught by the sdoc skill. The daemon write path replaced the earlier per-command whole-corpus reload; when external activity makes held state suspect, the explicit recovery is scribe reload followed by scribe check.

Retyped from SLICE to WORK on 2026-08-30 under DEC-SLICE-DECOMPOSES-TO-WORK and DEC-NODE-FAMILIES. The UID keeps its retired prefix under DEC-UID-OUTLIVES-TYPE.
<<<
RELATIONS:
- TYPE: Parent
  VALUE: DEC-EXECUTABLE-RULES-ROADMAP
  ROLE: Governed_By
- TYPE: Parent
  VALUE: MECH-RUNTIME-WRITE-GUARD
  ROLE: Crosses
- TYPE: Parent
  VALUE: MECH-SDOC-EDIT-VIA-MODEL
  ROLE: Crosses
- TYPE: Parent
  VALUE: MECH-SDOC-LEAN-FORMATS
  ROLE: Crosses
- TYPE: Parent
  VALUE: MECH-SDOC-CACHE-DIR-FOR-WORKTREES
  ROLE: Crosses
- TYPE: Parent
  VALUE: MECH-FILE-RELATION-EXISTENCE
  ROLE: Crosses
- TYPE: Parent
  VALUE: SLICE-GRAMMAR-FROM-NIX
  ROLE: Assumes
- TYPE: Parent
  VALUE: SPIKE-EXECUTABLE-RULES
  ROLE: Proven_By
- TYPE: File
  VALUE: dev/scripts/scribe_verbs.py
