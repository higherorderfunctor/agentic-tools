[DOCUMENT]
TITLE: Turn the scribe command into a client that fails closed

[GRAMMAR]
IMPORT_FROM_FILE: @repo

[WORK]
UID: WORK-SCRIBE-CLIENT
TITLE: Turn the scribe command into a client that fails closed
DEPTH: implemented
AUTHORED_BY: llm
STATEMENT: >>>
scribe is a thin command client over the resident daemon. It scans guarded flags before connecting, requests workspace.grammar to build the selected command surface, resolves file-backed argument values locally, and sends show, list, check, new, set, relate, unrelate, move, and delete as typed scribe.apply operations. It never loads the corpus or grammar file and has no fallback when the daemon is absent; the refusal names the socket and the command that starts one. The semantics subcommand remains a separate operator-owned model read and does not claim to validate the corpus.
<<<
NOTES: >>>
Implemented in the daemon stack. scribe_client.py owns root and socket discovery, the served-root assertion, and the fail-closed transport refusal. scribe_cmd.py obtains the grammar contract and turns argv into operations. scribe_ops.py applies those operations to scribe_workspace.py, so commands no longer load or verify a second graph in the client process.
<<<
RELATIONS:
- TYPE: Parent
  VALUE: DEC-SCRIBE-DAEMON-NO-FALLBACK
  ROLE: Governed_By
- TYPE: Parent
  VALUE: MECH-SCRIBE-RPC
  ROLE: Crosses
- TYPE: Parent
  VALUE: MECH-SCRIBE-SOCKET-IDENTITY
  ROLE: Crosses
- TYPE: File
  VALUE: dev/scripts/scribe_client.py
