[DOCUMENT]
TITLE: The register is not the source of truth it claims to be

[GRAMMAR]
IMPORT_FROM_FILE: @repo

[EVIDENCE]
UID: INV-REGISTER-NOT-AUTHORITATIVE
TITLE: The register is not the source of truth it claims to be
AUTHORED_BY: llm
STATEMENT: >>>
Seven open-card identifiers appear in section bodies with no register row at
all. One of them states a hard blocker cited by four sections and therefore
carries no retirement condition. Two register rows named as pointer-only appear
as no card anywhere.
<<<
RATIONALE: >>>
The register asserts that review state lives nowhere else. It does. Any
conversion that trusts the register as the complete decision set will silently
drop seven decisions.
<<<
PARENT_FP: DEC-CONVERT-IS-ADJUDICATION:0000000
NOTES: >>>
Retyped from INVARIANT to EVIDENCE on 2026-08-30 (it records a measurement, not a rule; DEC-NODE-FAMILIES). The UID keeps its retired prefix: DEC-UID-OUTLIVES-TYPE.
<<<
RELATIONS:
- TYPE: Parent
  VALUE: DEC-CONVERT-IS-ADJUDICATION
  ROLE: Governed_By
