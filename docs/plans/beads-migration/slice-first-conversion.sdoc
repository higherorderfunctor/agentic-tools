[DOCUMENT]
TITLE: First conversion target is the lane-iteration cluster

[GRAMMAR]
IMPORT_FROM_FILE: @repo

[WORK]
UID: SLICE-FIRST-CONVERSION
TITLE: First conversion target is the lane-iteration cluster
AUTHORED_BY: llm
STATEMENT: >>>
Convert 12-flow-iterate, 13-flow-settle and 14-flow-kill. 426 lines, roughly 60
nodes: one SLICE, ~26 MECHANISM, 13 INVARIANT from the grain rules, ~15
DECISION, ~4 SPIKE.
<<<
RATIONALE: >>>
Measured as the only multi-file design cluster carrying zero references to the
fleet-shape hinge, which is the corpus's largest instability with 22
localizations across 20 files. 14-flow-kill states outright that the hinge does
not reopen the flow. Eight dead out-edges against eighteen for the nearest
alternative, and six of the eight become live once register rows are nodes.
Two of its own open items dissolve rather than transfer if it is built host-side
first, which the corpus already offers as an escape hatch.
<<<
PARENT_FP: DEC-CONVERT-IS-ADJUDICATION:0000000
NOTES: >>>
Retyped from SLICE to WORK on 2026-08-30 under DEC-SLICE-DECOMPOSES-TO-WORK and DEC-NODE-FAMILIES. The UID keeps its retired prefix: DEC-UID-OUTLIVES-TYPE.
<<<
RELATIONS:
- TYPE: Parent
  VALUE: DEC-CONVERT-IS-ADJUDICATION
  ROLE: Governed_By
- TYPE: Parent
  VALUE: DEC-HITL-IS-THE-VIEWER
  ROLE: Assumes
