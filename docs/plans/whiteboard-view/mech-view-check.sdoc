[DOCUMENT]
TITLE: The view check: the rules a tree of narratives must satisfy that strictdoc does not check

[GRAMMAR]
IMPORT_FROM_FILE: @repo

[MECHANISM]
UID: MECH-VIEW-CHECK
TITLE: The view check: the rules a tree of narratives must satisfy that strictdoc does not check
DEPTH: implemented
AUTHORED_BY: llm
STATEMENT: >>>
view-check.py validates the narrative-tree rules that StrictDoc does not check and returns one finding list shared with wireline.py. It asks the resident daemon for workspace.grammar, validates the scribe-grammar/1 reply, and fails closed with the shared NoDaemon remedy instead of parsing grammar.sgra or loading a second graph. Its rules cover Contains tree shape, narrative types and placement, widget statement shapes, legends and shared colours, declared tabs and systems, query words, superseded citations, narrative dependency direction, and link resolution.

The current branch still walks the worktree to map exported UIDs to declaring files because R2 lands that path separately in the daemon export. That temporary provenance join is named by the daemon-only-source guard and disappears when the stacks combine.
<<<
RATIONALE: >>>
These are semantic-layer rules in a script (DEC-LAYER-STACK). They are allowed there for now on the operator's ruling that validation need not be modelled on joints yet, provided each is INDEXED -- which NAR-WHITEBOARD-VIEW-RULES does, so the porting inventory is a screen of the view.
<<<
RELATIONS:
- TYPE: Parent
  VALUE: DEC-NARRATIVE-IS-THE-VIEW-NODE
  ROLE: Governed_By
- TYPE: Parent
  VALUE: REQ-NOTHING-DEPENDS-ON-A-NARRATIVE
  ROLE: Guarantees
- TYPE: File
  VALUE: docs/sdoc/view/view-check.py
