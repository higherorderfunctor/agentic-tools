[DOCUMENT]
TITLE: What the node-type migration did to each node, in two passes

[GRAMMAR]
IMPORT_FROM_FILE: @repo

[EVIDENCE]
UID: EV-GRID-MIGRATION-LEDGER
TITLE: What the node-type migration did to each node, in two passes
AUTHORED_BY: llm
SOURCE: the retype scripts of the session and the mood-test workflow's verdicts (wf_9c9bcb70-975); every retype is also recorded in the node's own NOTES
STATEMENT: >>>
FIRST PASS (2026-08-30, by grammar type; 34 nodes, tag changed, UID kept):
  INV-DECISIONS-ARRIVE-AS-CARDS: INVARIANT -> REQUIREMENT
  INV-FILE-DO-NOT-NARRATE: INVARIANT -> REQUIREMENT
  INV-GUARDS-MUST-EXECUTE: INVARIANT -> REQUIREMENT
  INV-LISTS-WHERE-THE-READER-UNPACKS: INVARIANT -> REQUIREMENT
  INV-SETTLED-STAYS-VISIBLE: INVARIANT -> REQUIREMENT
  INV-REGISTER-NOT-AUTHORITATIVE: INVARIANT -> EVIDENCE
  INV-VOCABULARIES-UNBOUNDED: INVARIANT -> EVIDENCE
  SLICE-FIRST-CONVERSION: SLICE -> WORK
  SPIKE-CONVERSION-SIGNAL: SPIKE (unrun) -> WORK
  SPIKE-CORPUS-LINK-ROT: SPIKE (run) -> EVIDENCE
  SPIKE-CORPUS-NOT-NARRATIVE: SPIKE (run) -> EVIDENCE
  SPIKE-CORPUS-STALE-INVENTORY: SPIKE (run) -> EVIDENCE
  SPIKE-CORPUS-SYMBOL-LAYER: SPIKE (run) -> EVIDENCE
  INV-NO-EXTERNAL-PLAN-REFS: INVARIANT -> REQUIREMENT
  MECH-SEMANTIC-LAYER-WHITEBOARD: MECHANISM -> NARRATIVE (self-declared)
  SLICE-BEHAVIOUR-MODEL: SLICE -> WORK
  SLICE-CHECKPOINT-WIRING: SLICE -> WORK
  SLICE-FP-DETECTOR: SLICE -> WORK
  SLICE-GRAMMAR-FROM-NIX: SLICE -> WORK
  SLICE-GRAPH-CHECKS: SLICE -> WORK
  SLICE-HOOK-LAYER: SLICE -> WORK
  SLICE-INSTANCE-SEMANTICS-MIGRATION: SLICE -> WORK
  SLICE-RESTACK-TO-PRS: SLICE -> WORK
  SLICE-SDOC-CLI: SLICE -> WORK
  SLICE-SDOC-IN-SEMBLE: SLICE -> WORK
  SLICE-SEMANTIC-LAYER-RENDER: SLICE -> WORK
  SLICE-STRICTDOC-OVERLAY: SLICE -> WORK
  SLICE-WORKFLOW-DSL: SLICE -> WORK
  SPIKE-DECISION-ACCEPTANCE-PATH: SPIKE (run) -> EVIDENCE
  SPIKE-DSL-PRIOR-ART: SPIKE (run) -> EVIDENCE
  SPIKE-EXECUTABLE-RULES: SPIKE (run) -> EVIDENCE
  SPIKE-INCREMENTAL-EXPORT-FALSE-GREEN: SPIKE (unrun) -> WORK
  SPIKE-RIPPLE-SELECTOR-AST: SPIKE (unrun) -> WORK
  SPIKE-SGRA-PARSE: SPIKE (run) -> EVIDENCE

SECOND PASS (2026-08-30, the mechanism mood test over 135 MECHANISM nodes: 10 classifiers, then a second opinion arguing both sides on every proposed retype; 27 applied at high or medium confidence, 4 held at low confidence, 104 stayed MECHANISM):
  MECH-AUTHORED-BY-REWRITE-DRIFT: MECHANISM -> EVIDENCE (high)
  MECH-DEFAULT-EXPORT-IS-RED-ON-RST: MECHANISM -> EVIDENCE (medium)
  MECH-DIRTY-EDGE-ON-OPTION-CHANGE: MECHANISM -> REQUIREMENT (medium)
  MECH-EDGE-MAP-TABLE-RECONCILE: MECHANISM -> EVIDENCE (high)
  MECH-FAITHFUL-IS-NOT-A-CONSUMER-WORD: MECHANISM -> REQUIREMENT (high)
  MECH-FP-RELATION-LINT: MECHANISM -> REQUIREMENT (high)
  MECH-GROOM-CONTRADICTION-CHECK: MECHANISM -> REQUIREMENT (high)
  MECH-LANE-DISCIPLINE-IS-A-REQUIREMENT: MECHANISM -> REQUIREMENT (high)
  MECH-M4-CLAIMS-REFUTED-AGAINST-THE-TREE: MECHANISM -> EVIDENCE (high)
  MECH-MILESTONE-TWO-SEMANTICS-MISPLACED: MECHANISM -> EVIDENCE (medium)
  MECH-NODE-CODE-LINKAGE-IS-PROSE: MECHANISM -> EVIDENCE (medium)
  MECH-ONE-NODE-PER-FILE: MECHANISM -> REQUIREMENT (high)
  MECH-OVERLAY-PYTHON-OVERRIDE-SEAM: MECHANISM -> EVIDENCE (medium)
  MECH-OVERLAY-WRAPPING-BELONGS-IN-MODULES: MECHANISM -> REQUIREMENT (medium)
  MECH-PEG-REACHABILITY-COUNT: MECHANISM -> EVIDENCE (high)
  MECH-PLAN-CHANGE-KINDS: MECHANISM -> REQUIREMENT (medium)
  MECH-PROJECT-HOOKS-ABSENT-IN-WORKTREES: MECHANISM -> EVIDENCE (high)
  MECH-RENDER-GENERATOR-OUTSIDE-REPO: MECHANISM -> EVIDENCE (medium)
  MECH-SDOC-CLI-COVERS-STRICTDOC-SILENCE: MECHANISM -> REQUIREMENT (medium)
  MECH-SDOC-CONFIG-HOOK-IMPORTABILITY: MECHANISM -> EVIDENCE (medium)
  MECH-SDOC-LOOP-SHELL-ENTRY-STAGES-FILES: MECHANISM -> EVIDENCE (medium)
  MECH-SDOC-SKILL-CORRECTIONS: MECHANISM -> EVIDENCE (high)
  MECH-SDOC-VOCABULARY-SINGLE-SOURCE: MECHANISM -> EVIDENCE (medium)
  MECH-SGRA-BODY-COVERAGE: MECHANISM -> EVIDENCE (high)
  MECH-STRICTDOC-CLOSURE-TRIM: MECHANISM -> EVIDENCE (medium)

HELD for the operator (low confidence; each needs a split into a rule and a design, which is authoring, not retyping):
  MECH-AI-STRICTDOC-HOME-PARITY: proposed REQUIREMENT -- What would split it: (1) DECISION, once expressible: 'home-manager module carries enable and package only; grammars is not mirrored because it is project-scoped'. (2) REQUIREMENT / parity-rule amendme
  MECH-CI-UP-TO-PAR-BEFORE-MERGE: proposed REQUIREMENT -- Really a DECISION plus a WORK item; REQUIREMENT is the nearest available verdict on the normative axis only. Split: DECISION -- 'additional CI tooling is not required for the bulk of this experiment; 
  MECH-HTML-RENDER-MUST-PASS: proposed REQUIREMENT -- Genuinely half rule, half design; the split is the real answer. Split: REQUIREMENT 'the corpus renders to HTML' (paragraph 1 + RATIONALE) and MECHANISM 'the render gate invokes strictdoc's own field p
  MECH-SEMBLE-TEST-RECIPE: proposed EVIDENCE -- Genuinely mixed. What would split it: an EVIDENCE node for the PYTHONPATH-shadowing finding (measured on SLICE-SDOC-IN-SEMBLE, one false defect report caused) plus a WORK item for the recipe. If the o
<<<
NOTES: >>>
Every retyped node keeps its UID (DEC-UID-OUTLIVES-TYPE) and carries the retype and its reason in NOTES, so this ledger is a convenience, not the record. The review a person can rule from is NAR-MECHANISM-MOOD-REVIEW in the strictdoc-tooling plan.
<<<
