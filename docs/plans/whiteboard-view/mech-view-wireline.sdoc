[DOCUMENT]
TITLE: The wireline: one versioned JSON payload per root, computed from the export by a backed script

[GRAMMAR]
IMPORT_FROM_FILE: @repo

[MECHANISM]
UID: MECH-VIEW-WIRELINE
TITLE: The wireline: one versioned JSON payload per root, computed from the export by a backed script
DEPTH: implemented
AUTHORED_BY: llm
STATEMENT: >>>
wireline.py reads a StrictDoc JSON export and asks the resident scribe daemon for workspace.grammar, validating the scribe-grammar/1 reply before it builds the whiteboard-view/2 payload. Without a daemon it exits non-zero with the shared NoDaemon socket and start remedy; it never opens grammar.sgra or imports the grammar parser.

The payload carries generated provenance, systems, tabs, colours, narrative trees, node cards, relation edges, backlinks, the daemon-supplied grammar, choice ladders, view-check findings, and closed query tables. Field values pass through verbatim and computed values live under named keys. This branch still obtains UID provenance from view-check's worktree map until the separately landed R2 export-path commit is combined; the export JSON and daemon grammar remain the only graph and grammar inputs.
<<<
RATIONALE: >>>
A TUI reads the same payload as the page; the payload is the contract that keeps the viewer's form open (DEC-VIEWER-FORM-UNDECIDED) while the view exists.
<<<
RELATIONS:
- TYPE: Parent
  VALUE: DEC-VIEWS-ARE-REGENERABLE
  ROLE: Governed_By
- TYPE: Parent
  VALUE: DEC-NARRATIVE-IS-THE-VIEW-NODE
  ROLE: Governed_By
- TYPE: File
  VALUE: docs/sdoc/view/wireline.py
