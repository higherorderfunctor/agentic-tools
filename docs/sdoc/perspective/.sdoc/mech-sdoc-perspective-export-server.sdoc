[DOCUMENT]
TITLE: A read-only HTTP endpoint owns each ephemeral export

[GRAMMAR]
IMPORT_FROM_FILE: @repo

[MECHANISM]
UID: MECH-SDOC-PERSPECTIVE-EXPORT-SERVER
TITLE: A read-only HTTP endpoint owns each ephemeral export
DEPTH: implemented
AUTHORED_BY: llm
STATEMENT: >>>
A standard-library HTTP server serves an allowlisted static UI and a GET-only data endpoint. For each data request it creates a TemporaryDirectory, runs strictdoc export on the repository root with JSON as the sole format, reads json/index.json, adapts it while the directory exists, and then lets the temporary directory clean itself. Export and schema failures become structured non-success responses.
<<<
NOTES: >>>
Implemented 2026-08-31 with a standard-library threaded HTTP server, allowlisted assets, GET and HEAD data access, structured exporter failure responses, no-store data responses and a strict launcher that resolves the CLI without importing it.
<<<
RELATIONS:
- TYPE: Parent
  VALUE: DEC-SDOC-PERSPECTIVE-EXPORT-BOUNDARY
  ROLE: Governed_By
- TYPE: Parent
  VALUE: REQ-SDOC-PERSPECTIVE-FRESH-DATA
  ROLE: Guarantees
- TYPE: Parent
  VALUE: EV-SDOC-PERSPECTIVE-FIRST-EXPLORER
  ROLE: Proven_By
- TYPE: File
  VALUE: docs/sdoc/perspective/exporter.py
- TYPE: File
  VALUE: docs/sdoc/perspective/serve
- TYPE: File
  VALUE: docs/sdoc/perspective/server.py
