[DOCUMENT]
TITLE: Perspective explores the exported rows in the browser

[GRAMMAR]
IMPORT_FROM_FILE: @repo

[MECHANISM]
UID: MECH-SDOC-PERSPECTIVE-VIEWER
TITLE: Perspective explores the exported rows in the browser
DEPTH: implemented
AUTHORED_BY: llm
STATEMENT: >>>
The page loads pinned Perspective CDN modules for the viewer, datagrid, charts and browser worker, creates a named table from the response rows, and opens the native configuration panel over a dark themed datagrid. Perspective config-update events save its native JSON-ready token to localStorage; after the table schema is loaded, reload restores that object directly and falls back to the default view if restoration fails.
<<<
NOTES: >>>
Implemented 2026-08-31 against pinned Perspective 5.3.0 CDN modules. Headless Chromium rendered the Pro Dark Datagrid and proved that a native _NODE_TYPE group-by survived a fresh-export page reload through the viewer save and restore token.
<<<
RELATIONS:
- TYPE: Parent
  VALUE: DEC-SDOC-PERSPECTIVE-LOCAL-VIEW-STATE
  ROLE: Governed_By
- TYPE: Parent
  VALUE: EV-SDOC-PERSPECTIVE-FIRST-EXPLORER
  ROLE: Proven_By
- TYPE: File
  VALUE: docs/sdoc/perspective/assets/app.css
- TYPE: File
  VALUE: docs/sdoc/perspective/assets/app.js
- TYPE: File
  VALUE: docs/sdoc/perspective/index.html
