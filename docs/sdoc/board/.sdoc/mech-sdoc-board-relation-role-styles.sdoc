[DOCUMENT]
TITLE: Relation roles use evenly distributed solid colors

[GRAMMAR]
IMPORT_FROM_FILE: @repo

[MECHANISM]
UID: MECH-SDOC-BOARD-RELATION-ROLE-STYLES
TITLE: Relation roles use evenly distributed solid colors
AUTHORED_BY: llm
STATEMENT: >>>
The Graph view assigns each payload-derived relation role a deterministic hue
from the alphabetically sorted role vocabulary. A binary low-discrepancy
sequence spreads the growing set around the hue circle, beginning with orange,
while fixed OKLCH lightness and chroma keep the hues similarly legible on the
dark canvas. The same role name therefore keeps one color across
source-node-type filter groups, the grouped graph key, edge paths, labels, and
arrowheads. Color is an identity aid rather than normative meaning, and the
vocabulary remains payload-derived.

All relation paths are solid. Arrowheads preserve the relation's declared
source-to-target direction; there is no focal-relative outgoing, incoming, or
transit stroke category. Inspecting a card may emphasize or dim relevant paths,
but it does not change their hue or line pattern.
<<<
NOTES: >>>
Added by the Graph neighborhood reference implementation on 2026-09-02.
<<<
RELATIONS:
- TYPE: Parent
  VALUE: MECH-SDOC-BOARD-SCOPED-RELATION-FILTERS
  ROLE: Assumes
- TYPE: Parent
  VALUE: DEC-SDOC-BOARD-MVP-NATIVE-WEB
  ROLE: Governed_By
- TYPE: File
  VALUE: docs/sdoc/board/index.html
- TYPE: File
  VALUE: docs/sdoc/board/assets/app.css
- TYPE: File
  VALUE: docs/sdoc/board/assets/board.js
- TYPE: Parent
  VALUE: EV-SDOC-BOARD-GRAPH-KEY-AND-ROLE-STYLE-SMOKE
  ROLE: Proven_By
