[DOCUMENT]
TITLE: The Board canvas uses the native web platform behind replaceable seams

[GRAMMAR]
IMPORT_FROM_FILE: @repo

[DECISION]
UID: DEC-SDOC-BOARD-MVP-NATIVE-WEB
TITLE: The Board canvas uses the native web platform behind replaceable seams
AUTHORED_BY: llm
STATUS: accepted
RETIRES_ON: Measured board usage requires a component, layout, or rendering library whose benefit exceeds the app's build and dependency cost.
STATEMENT: >>>
The Board canvas is dependency-free HTML, CSS and JavaScript over SVG. Data
adaptation, layout and rendering remain separate modules communicating through
application-owned plain objects, so a heavier canvas (React Flow and ELK, say)
can replace the drawing without replacing the server, the adapter, or the
snapshot schema. The Perspective view is the ruled exception, and its
dependency is pinned and governed separately
(DEC-SDOC-BOARD-PERSPECTIVE-FROM-CDN).
<<<
RATIONALE: >>>
The operator asked first to see the whole canon with no filtering or mutation
and expects to reshape the result. A zero-build canvas reaches that probe
directly while keeping the durable boundary: canon source, owned snapshot,
layout, renderer.
<<<
NOTES: >>>
Ported 2026-09-01 from the codex spike branch, narrowed from "the MVP browser"
to the Board canvas when the Perspective view joined the app.

2026-09-08, reconciling the ported Graph view against this tree: the
"dependency-free" clause no longer describes the canvas. ELK.js 0.12.0 became
the Graph view's layout and edge-routing engine on 2026-09-02 under
the Graph neighborhood delivery, and since 2026-09-08 it arrives from Nix rather
than from the tree. The seam this decision exists to
protect held: adapter, layout and renderer stayed separate modules over plain
objects, and taking the dependency touched neither the server nor the snapshot
schema. Nothing is retired here. MECH-SDOC-BOARD-LAYOUT describes the
dependency, and whether the RETIRES_ON condition is now met is the operator's
call.
<<<
